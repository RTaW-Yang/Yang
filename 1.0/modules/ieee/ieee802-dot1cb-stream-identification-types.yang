module ieee802-dot1cb-stream-identification-types {
 yang-version "1.1";
 namespace
 urn:ieee:std:802.1Q:yang:ieee802-dot1cb-stream-identification-types;
 prefix dot1cb-sid-types;
 organization
 "Institute of Electrical and Electronics Engineers";
 contact
 "WG-URL: http://ieee802.org/1/
 WG-EMail: stds-802-1-l@ieee.org

 Contact: IEEE 802.1 Working Group Chair
 Postal: C/O IEEE 802.1 Working Group
 IEEE Standards Association
 445 Hoes Lane
 Piscataway, NJ 08854
 USA

 E-mail: stds-802-1-chairs@ieee.org";
 description
 "Management objects that control the stream identification from IEEE
 Std 802.1CB-2017. This YANG data model conforms to the Network
 Management Datastore Architecture defined in RFC 8342. Copyright (C)
 IEEE (2021). This version of this YANG module is part of IEEE Std
 802.1CBcv; see the draft itself for full legal notices.";
 revision 2021-05-06 {
 description
 "Published as part of IEEE Std 802.1CBcv-2021. Initial version.";
 reference
 "IEEE Std 802.1CBcv-2021, Frame Replication and Elimination for
 Reliability - FRER YANG Data Model and Management Information Base
 Module.";
 }
 identity strid-idty {
 description
 "Root identity for all stream identification types";
 }
 typedef direction {
 type boolean;
 description
 "A boolean object indicating whether the direction is out-facing
 (True) or in-facing (False).";
 reference
 "10.4.1.3 of IEEE Std 802.1CB-2017";
 }
 typedef stream-id-function {
 type enumeration {
 enum reserved {
 value 0;
 description
 "Reserved value.";
 }
 enum null-stream {
 value 1;
 description
 "The stream identification type used for the Null Stream
 identification method.";
 }
 enum smac-vlan {
 value 2;
 description
 "The stream identification type used for the Source MAC and
 VLAN Stream identification method.";
 }
 enum dmac-vlan {
 value 3;
 description
 "The stream identification type used for the Active Destination
 MAC and VLAN Stream identification method.";
 }
 enum ip {
 value 4;
 description
 "The stream identification type used for the IP Stream
 identification method.";
 }
 }
 description
 "An enumerated value indicating the method used to identify packets
 belonging to a Stream.";
 reference
 "9.1.1.6 of IEEE Std 802.1CB-2017";
 }
}
